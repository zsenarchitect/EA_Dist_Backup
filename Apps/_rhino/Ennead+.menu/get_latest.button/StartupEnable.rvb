Option Explicit

Sub StartupEnable()
    Dim filePath
    Dim userFolder
    
    userFolder = CreateObject("WScript.Shell").ExpandEnvironmentStrings("%USERPROFILE%")
    filePath = userFolder & "\Documents\EnneadTab Ecosystem\EA_Dist\Apps\_rhino\Ennead+.menu\get_latest.button\StartupCaller.rvb"
    
    ' Ensure path with spaces is handled correctly by enclosing in quotes
    filePath = """" & filePath & """"
    
    Call Rhino.AddStartupScript(filePath)
End Sub

Call StartupEnable()
